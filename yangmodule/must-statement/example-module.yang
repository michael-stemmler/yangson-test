module example-module {

   namespace "http://example.com/ns/example-module";
   prefix "mod";

   organization "Example.";
   contact "support at example.com";
   description "";
   revision "2019-02-18" {
     description "Initial version.";
     reference "456";
   }

   container container1 {
        list list-a {
            key name;
            leaf name {
                type string;
            }
            leaf identifier {
                type string;
            }
        }
   }

   container container2 {
        list list-b {
            key name;
            leaf name {
                type string;
            }
            leaf identifier {
                type string;
            }

            leaf list-a-name {
                type string;
                must "/mod:container1/mod:list-a[mod:name=.]/mod:identifier=../identifier"{
                description
                "The 'identifier' in list-a must be the same as the 'identifier'
                configured here.";
                }
            }
        }
   }
}
